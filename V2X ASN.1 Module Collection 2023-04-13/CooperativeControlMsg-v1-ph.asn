--
-- Terms and Conditions and User License Agreement - Download and Use of ASN File
-- 
-- Copyright: Each ASN File contained herein ("File") is copyrighted and all
-- rights, title, and interest in and to each File are owned by SAE. The 
-- license contained herein applies to each File and each reference in this license
-- to "the File" or "this File" shall be construed to include each and any ASN File
-- contained herein. No rights therein are granted except as set forth in this
-- License. Any copying, transmission, modification or reproduction of the File or
-- the copyrighted material within it, in part or in whole, except as herein
-- permitted is cause for revocation of this License.
-- 
-- License: SAE International ("SAE") hereby grants to you, as an individual or as
-- a single corporate entity, a limited nonexclusive, nontransferable right to
-- download this File in an electronic format for your individual use or use by
-- a single corporate entity on one computer. One hard copy of the File can also
-- be printed for individual use or use by a single corporate entity. SAE also
-- hereby grants to you the nonexclusive, nontransferable right to use this File
-- and create derivative works using this File for your own or your own corporate
-- entity's research purposes and in the design, creation, manufacture, distribution,
-- and use of your own products. For purposes of clarification, derivative works
-- permitted under this license include derivative works or source code that do not
-- include or incorporate this File. The derivative work may use the File to create
-- source code and corresponding software programs.  Notwithstanding the foregoing,
-- you agree that you must obtain a license from SAE to create any derivative works
-- which incorporate this File or its contents.
--
-- SAE also hereby grants to you the nonexclusive, nontransferable right to copy,
-- reproduce, distribute to others the derivative works from the use of the content
-- of this File or portions thereof in or as part of your company's products.
-- You must only license, and not otherwise sell or transfer, the products, software,
-- and software documentation that incorporates content from this File, and you must
-- prohibit any licensees or others from transferring, copying, or extracting the
-- contents of this File thereof for use in their own or others' software or products.
--
-- Other than as expressly permitted herein, this File may not be copied in whole in
-- any form for distribution to other users or other computers, including without
-- limitation to other individuals or users within your own corporate entity or
-- outside your corporate entity.  This license prohibits the end user from posting
-- or distributing content via any public forum or as open access content.  If other
-- individuals in or outside your corporate entity or different cooperate entities,
-- whether related or not to your corporate entity, wish to download or copy this
-- File, they must purchase a separate individual license to do so. 
-- 
-- This File is licensed "AS IS" to you and you do hereby hold SAE harmless from your
-- use of the File or the creative or use of derivative works thereof, and you agree
-- to indemnify SAE from any and all claims or damages caused by your use,
-- reproduction, distribution to others, or application of this File or any
-- derivative works therefrom.  SAE may amend the terms of and conditions of
-- this License or cancel this License at any time in its sole discretion and
-- for any reason by reasonable notice, including without limitation by posting
-- revised terms on its website.  
--
-- General: Files that have been successfully downloaded cannot be returned for
-- refund or credit. This Agreement is the complete and exclusive statement of the
-- agreement between you and SAE and supersedes any and all prior agreements or
-- understandings, either written or oral, concerning the subject of this Agreement.
-- Any modifications must be in writing and signed by the parties.
-- 
-- Notice to Resellers: Authorized resellers of SAE Files may download this File on
-- behalf of their customers and forward it directly, unopened, to their customers
-- provided their customers agree to abide by the terms of this License. Resellers
-- may not otherwise copy, transmit, modify or reproduce this File.
-- 
-- This license will remain in effect for the life of the standards associated with
-- the File unless otherwise amended or cancelled by SAE in its sole discretion.
-- In the event that the associated standard is cancelled or recalled due to interest
-- of public safety, the aforementioned License will be rescinded as well. This 
-- License shall terminate upon violation of any of its terms.
--
-- (C)2022 SAE International.  All rights reserved.  SAE International retains the
-- right to entertain or negotiate requests for customized distribution agreements
-- for multi-user or corporate use and / or distribution. Requests should be submitted
-- to customerservice@sae.org.
--

-- This is a placeholder file for the fully defined ASN.1 module. 
-- Replace this file with the correct SAE file to compile a functional module.

CooperativeControlMessage 
{joint-iso-itu-t (2) country (16) us (840) organization (1) sae (114566) 
v2x-communications (1) technical-committees (1) v2x-core (5) technical-reports (1) 
j2735 (2735) part-0 (0) asn1-module (1) cooperativeControlMessage (40) 
version-1 (1) version-minor-0 (0)}

DEFINITIONS AUTOMATIC TAGS ::=
BEGIN
       
CooperativeControlMessage ::= NULL
  
END
